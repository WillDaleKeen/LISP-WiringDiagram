(defun C:prnt()

	(setq SONumber (substr JobNumber 1 6))
	(setq FileName (strcat JobName " - " JobNumber))
	(setq JobFolder (strcat DrawingFolder "/ELECTRICAL - " JobName " - " SONumber))
	(IF (NOT (vl-file-directory-p JobFolder)) (vl-mkdir JobFolder))
	(setq SaveFile (strcat JobFolder "/" FileName))
	(command "saveas" "2013" SaveFile)

	(setq PowerPageName (strcat JobFolder "/" FileName " - Power, Rev. A.pdf"))
	(command "-plot" "N" "Power" "11x17 DWG Print" "DWG to PDF.pc3" PowerPageName "Y" "Y")
	(setq Ctrls1PageName (strcat JobFolder "/" FileName " - CTRLS1, Rev. A.pdf"))
	(command "-plot" "N" "CTRLS 1" "11x17 DWG Print" "DWG to PDF.pc3" Ctrls1PageName "Y" "Y")
	(setq LegendPageName (strcat JobFolder "/" FileName " - Legend and Key, Rev. A.pdf"))
	(command "-plot" "N" "LEGEND & KEY" "8.5x11 Portrait" "DWG to PDF.pc3" LegendPageName "Y" "Y")
	(COND ((OR (AND (OR (= (substr MN 17 1) "M")
	                    (= (substr MN 17 1) "P")
	                    (= (substr MN 17 1) "S")
	                    (= (substr MN 17 1) "U")
		        )
	                (OR (= (substr MN 16 1) "A")
		            (= (substr MN 16 1) "D")
		        )
	            )
	            (OR (= (substr MN 5 3) "035")
		        (= (substr MN 5 3) "040")
		        (= (substr MN 5 3) "045")
		        (= (substr MN 5 3) "050")
		        (= (substr MN 5 3) "055")
		        (= (substr MN 5 3) "060")
		        (= (substr MN 5 3) "070")
		        (= (substr MN 5 3) "080")
		    )
	       )
	       (setq Ctrls2Page (strcat FileDirectory "/" FileName " - CTRLS2, Rev. A"))
	       (command "-plot" "N" "CTRLS 2" "11x17 DWG Print" "DWG to PDF.pc3" Ctrls2Page "N" "Y" "")
	      )
	      (t nil)
	      )
)
